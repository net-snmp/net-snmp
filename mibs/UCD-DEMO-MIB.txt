UCD-DEMO-MIB DEFINITIONS ::= BEGIN

IMPORTS
   MODULE-IDENTITY, OBJECT-TYPE,
   OBJECT-IDENTITY,
   MODULE-COMPLIANCE, OBJECT-GROUP       FROM SNMPv2-CONF
   ucdavis                               FROM UCD-SNMP-MIB;

ucdDemoMIB MODULE-IDENTITY
   LAST-UPDATED "9812040000Z"            -- 04 December 1998
   ORGANIZATION "UCDavis"
   CONTACT-INFO "The ucd-snmp-coders mailing list is the best place to 
                 write for public questions about the ucd-snmp
                 project: ucd-snmp-coders@ece.ucdavis.edu

                 Primary Author: Wes Hardaker

                 postal:     IT-DCAS
                             UCDavis
	                     Davis CA  95616
                 phone:      +1 530 754-7571
                 email:      wjhardaker@ucdavis.edu
                "
   DESCRIPTION  "The UCD-SNMP Demonstration MIB"
   ::= { ucdavis 14 }

ucdDemoMIBObjects
   OBJECT IDENTIFIER ::= { ucdDemoMIB 1 }

ucdDemoPublic OBJECT IDENTIFIER ::= { ucdDemoMIBObjects 1 }

ucdDemoResetKeys  OBJECT-TYPE
   SYNTAX       Integer32 (0..2147483647)
   MAX-ACCESS   read-write
   STATUS       current
   DESCRIPTION "A set of value 1 to this object resets the
                demonstration user's auth and priv keys to the
                keys based on the P->Ku->Kul transformation of the
                value of the ucdDemoPasspharse object.

	        Values other than 1 are ignored.
	       "
   ::= { ucdDemoPublic 1 }

ucdDemoPublicString  OBJECT-TYPE
   SYNTAX       OCTET STRING (SIZE(0..1024))
   MAX-ACCESS   read-write
   STATUS       current
   DESCRIPTION "A publicly settable string that can be set for testing 
                snmpsets.  This value has no real usage other than
                testing purposes.
	       "
   ::= { ucdDemoPublic 2 }

ucdDemoUserList  OBJECT-TYPE
   SYNTAX       OCTET STRING
   MAX-ACCESS   read-only
   STATUS       current
   DESCRIPTION "The list of users affected by the ucdDemoResetKeys object.
	       "
   ::= { ucdDemoPublic 3 }

ucdDemoPassphrase  OBJECT-TYPE
   SYNTAX       OCTET STRING
   MAX-ACCESS   read-only
   STATUS       current
   DESCRIPTION "The demo passphrase that ucdDemoResetKeys changes each 
                users localized key to based on the P->Ku->Kul transformation.
	       "
   ::= { ucdDemoPublic 4 }

END
