IPSEC-MIB DEFINITIONS ::= BEGIN

   IMPORTS
       MODULE-IDENTITY, OBJECT-TYPE, Counter32, Gauge32, Counter64,
       Integer32, mib-2, experimental,
       NOTIFICATION-TYPE                        FROM SNMPv2-SMI
       TEXTUAL-CONVENTION, DateAndTime,
       TruthValue                               FROM SNMPv2-TC
       MODULE-COMPLIANCE, OBJECT-GROUP          FROM SNMPv2-CONF
       snmpTraps                                FROM SNMPv2-MIB
       IANAifType                               FROM IANAifType-MIB;

   ipsecMIB MODULE-IDENTITY
       LAST-UPDATED "????"
       ORGANIZATION "IETF IPSec Working Group"
       CONTACT-INFO
               "   Tim Jenkins
                   TimeStep Corporation
                   362 Terry Fox Drive
                   Kanata, ON  K0A 2H0
                   Canada

                   613-599-3610
                   tjenkins@timestep.com"

       DESCRIPTION
               "The MIB module to describe generic IPSec objects
                and transient and permanent virtual tunnels created
                by IPSec SAs."
       REVISION      "????"
       DESCRIPTION
               "Initial revision."
--          ::= { mib-2 ?? }
	    ::= { experimental 75 }


   ipsecMIBObjects OBJECT IDENTIFIER ::= { ipsecMIB 1 }

   ipsec      OBJECT IDENTIFIER ::= { ipsecMIBObjects 1 }




-- the IPSec IKE MIB-Group
--
-- a collection of objects providing information about
-- IPSec's IKE SAs


ipsecIkeSaTable OBJECT-TYPE
    SYNTAX     SEQUENCE OF IpsecIkeSaEntry
    MAX-ACCESS not-accessible
    STATUS     current
    DESCRIPTION
            "The (conceptual) table containing information on
             IPSec's IKE SAs."
    ::= { ipsec 1 }

ipsecIkeSaEntry OBJECT-TYPE
    SYNTAX     IpsecIkeSaEntry
    MAX-ACCESS not-accessible
    STATUS     current
    DESCRIPTION
            "An entry (conceptual row) containing the information
             on a particular IKE SA."
    INDEX      { ipsecIkeSaIndex }
    ::= { ipsecIkeSaTable 1 }

IpsecIkeSaEntry ::= SEQUENCE {
   ipsecIkeSaIndex                  Integer32,

-- security algorithm information
   ipsecIkeSaEncAlg                 INTEGER,
   ipsecIkeSaEncLeyLength           Integer32,
   ipsecIkeSaHashAlg                Integer32,
   ipsecIkeSaDifHelGroupDesc        Integer32,
   ipsecIkeSaDifHelGroupType        Integer32,
   ipsecIkeSaDifHelFieldSize        Integer32,
   ipsecIkeSaPRF                    Integer32,
   ipsecIkeSaPFS                    TruthValue,

-- peer information
   ipsecIkeSaPeerIpAddress          IpAddress,
   ipsecIkeSaAuthMethod             Integer32,
   ipsecIkeSaPeerIdType             Integer32,
   ipsecIkeSaPeerId                 OCTET STRING,

-- virtual link status
   ipsecIkeSaType                   INTEGER,
   ipsecIkeSaStatus                 INTEGER,

-- expiration limits, current SA
   ipsecIkeSaTimeStart              DateAndTime,
   ipsecIkeSaTimeLimit              Counter32,
   ipsecIkeSaTrafficLimit           Counter32,

-- current operating statistics
   ipsecIkeSaInboundTraffic         Counter64,  -- in bytes
   ipsecIkeSaOutboundTraffic        Counter64,  -- in bytes

-- aggregate statistics
   ipsecIkeSaTotalSaNum             Counter32
   ipsecIkeSaTotalTime              Counter32,
   ipsecIkeSaTotalInboundTraffic    Counter64,  -- in bytes
   ipsecIkeSaTotalOutboundTraffic   Counter64,  -- in bytes

-- aggregate error statistics
   ipsecIkeSaDecryptErrors          Counter32,
   ipsecIkeSaHashErrors             Counter32,

-- IPSec SA (Phase 2) statistics (aggregate)
   ipsecIkeSaIpsecInboundTraffic    Counter64,
   ipsecIkeSaIpsecOutboundTraffic   Counter64,

-- IPSec SA (Phase 2) error statistics (aggregate)
   ipsecIkeSaIpsecDecryptErrors     Counter32,
   ipsecIkeSaIpsecAuthErrors        Counter32,
   ipsecIkeSaIpsecReplayErrors      Counter32,

}

ipsecIkeSaIndex OBJECT-TYPE
    SYNTAX      Integer32 (1..2147483647)
    MAX-ACCESS  read-only
    STATUS      current
    DESCRIPTION
            "A unique value, greater than zero, for each tunnel
             interface.  It is recommended that values are assigned
             contiguously starting from 1.

             The value for each tunnel interface must remain
             constant at least from one re-initialization of the
             entity's network management system to the next re-
             initialization.

             Further, the value for tunnel interfaces that are
             marked as permanent must remain constand across all
             re-initializations of the network management system."
    ::= { ipsecIkeSaEntry 1 }

ipsecIkeSaEncAlg OBJECT-TYPE
    SYNTAX      INTEGER
    MAX-ACCESS  read-only
    STATUS      current
    DESCRIPTION
            "A unique value representing the encryption algorithm
             applied to traffic carried by this SA or 0 if there
             is no encryption applied.

             Specific values are used as described in the ISAKMP
             Class Values of Encryption Algorithms from Appendix A
             of [IKE]."
    ::= { ipsecIkeSaEntry 2 }

ipsecIkeSaEncLeyLength OBJECT-TYPE
    SYNTAX      Integer32
    MAX-ACCESS  read-only
    STATUS      current
    DESCRIPTION
            "The length of the encryption key in bits used for the
             algorithm specified in the ipsecIkeSaEncAlg object,
             or 0 if the key length is implicit in the specified
             algorithm or there is no encryption specified."
    ::= { ipsecIkeSaEntry 3 }

ipsecIkeSaHashAlg OBJECT-TYPE
    SYNTAX      Integer32
    MAX-ACCESS  read-only
    STATUS      current
    DESCRIPTION
            "A unique value representing the hash algorithm
             applied to traffic carried by this SA or 0 if there
             is no encryption applied.

             Specific values are used as described in the ISAKMP
             Class Values of Hash Algorithms from Appendix A
             of [IKE]."
    ::= { ipsecIkeSaEntry 4 }

ipsecIkeSaDifHelGroupDesc OBJECT-TYPE
    SYNTAX      Integer32
    MAX-ACCESS  read-only
    STATUS      current
    DESCRIPTION
            "A unique value representing the Diffie-Hellman group
             description used or 0 if the group is unknown.

             Specific values are used as described in the ISAKMP
             Class Values of Group Description from Appendix A
             of [IKE]."
    ::= { ipsecIkeSaEntry 5 }

ipsecIkeSaDifHelGroupType OBJECT-TYPE
    SYNTAX      Integer32
    MAX-ACCESS  read-only
    STATUS      current
    DESCRIPTION
            "A unique value representing the Diffie-Hellman group
             type used or 0 if the group is unknown.

             Specific values are used as described in the ISAKMP
             Class Values of Group Type from Appendix A of [IKE]."
    ::= { ipsecIkeSaEntry 6 }

ipsecIkeSaDifHelFieldSize OBJECT-TYPE
    SYNTAX      Integer32
    MAX-ACCESS  read-only
    STATUS      current
    DESCRIPTION
            "The field size, in bits, of a Diffie-Hellman group."
    ::= { ipsecIkeSaEntry 7 }

ipsecIkeSaPRF OBJECT-TYPE
    SYNTAX      Integer32
    MAX-ACCESS  read-only
    STATUS      current
    DESCRIPTION
            "The pseudo-random functions used, or 0 if not used or
             if unknown.

             Specific values are used as described in the ISAKMP
             Class Values of PRF from Appendix A of [IKE]."
    ::= { ipsecIkeSaEntry 8 }

ipsecIkeSaPFS OBJECT-TYPE
    SYNTAX      TruthValue
    MAX-ACCESS  read-only
    STATUS      current
    DESCRIPTION
            "A value that indicates that perfect forward secrecy is
             used for all protocol SAs created by this IKE SA."
    ::= { ipsecIkeSaEntry 9 }

ipsecIkeSaPeerIpAddress OBJECT-TYPE
    SYNTAX      IpAddress
    MAX-ACCESS  read-only
    STATUS      current
    DESCRIPTION
            "The IP address of the peer that this SA was negotiated
            with, or 0 if unknown."
    ::= { ipsecIkeSaEntry 10 }

ipsecIkeSaAuthMethod OBJECT-TYPE
    SYNTAX      Integer32
    MAX-ACCESS  read-only
    STATUS      current
    DESCRIPTION
            "The authentication method used to authenticate the
             peers.

             Note that this does not include the specific method of
             authentication if extended authenticated is used.

             Specific values are used as described in the ISAKMP
             Class Values of Authentication Method from Appendix A
             of [IKE]."
    ::= { ipsecIkeSaEntry 11 }

ipsecIkeSaPeerIdType OBJECT-TYPE
    SYNTAX      Integer32
    MAX-ACCESS  read-only
    STATUS      current
    DESCRIPTION
            "The type of ID used by the peer.

             Specific values are used as described in
             Section 4.6.2.1 of [IPDOI]."
    ::= { ipsecIkeSaEntry 12 }

ipsecIkeSaPeerId OBJECT-TYPE
    SYNTAX      OCTET STRING (SIZE (0..511))
    MAX-ACCESS  read-only
    STATUS      current
    DESCRIPTION
            "The ID of the peer this SA was negotiated with.

             The length may require truncation under some
             conditions."
    ::= { ipsecIkeSaEntry 13 }

ipsecIkeSaType OBJECT-TYPE
    SYNTAX      INTEGER { transient(1), permanent(2) }
    MAX-ACCESS  read-only
    STATUS      current
    DESCRIPTION
            "The type of virtual tunnel represented by this row.

             A transient link will disappear from the table when
             the SAs needed for it cannot be established. A
             permanent link will shows its status in the
             ipsecIkeSaStatus object."
    ::= { ipsecIkeSaEntry 14 }

ipsecIkeSaStatus OBJECT-TYPE
    SYNTAX      INTEGER
                { never-tried(0), link-up(1), link-down(2) }
    MAX-ACCESS  read-only
    STATUS      current
    DESCRIPTION
            "The status of the virtual tunnel represented by this
             row, if the tunnel is configured as permanent.

             never-tried means that no attempt to set-up the link
             has been done. link-up means that the link is up and
             operating normally. link-down means that the link was
             up, but has gone down."
    ::= { ipsecIkeSaEntry 15 }

ipsecIkeSaTimeStart OBJECT-TYPE
    SYNTAX      DateAndTime
    MAX-ACCESS  read-only
    STATUS      current
    DESCRIPTION
            "The date and time that the current SA within the link
             was set up.

             It is not the date and time that the virtual tunnel
             was set up."
    ::= { ipsecIkeSaEntry 16 }

ipsecIkeSaTimeLimit OBJECT-TYPE
    SYNTAX      Counter32
    MAX-ACCESS  read-only
    STATUS      current
    DESCRIPTION
            "The maximum lifetime in seconds of the current SA
             supporting the virtual tunnel, or 0 if there is
             no time constraint on its expiration."
    ::= { ipsecIkeSaEntry 17 }

ipsecIkeSaTrafficLimit OBJECT-TYPE
    SYNTAX      Counter32
    MAX-ACCESS  read-only
    STATUS      current
    DESCRIPTION
            "The maximum traffic in 1024-byte blocks that the
             current SA supporting the virtual tunnel is allowd
             to support, or 0 if there is no traffic constraint
             on its expiration."
    ::= { ipsecIkeSaEntry 18 }

ipsecIkeSaInboundTraffic OBJECT-TYPE
    SYNTAX      Counter64
    MAX-ACCESS  read-only
    STATUS      current
    DESCRIPTION
            "The amount traffic measured in bytes handled in the
             current SA in the inbound direction."
    ::= { ipsecIkeSaEntry 19 }

ipsecIkeSaOutboundTraffic OBJECT-TYPE
    SYNTAX      Counter64
    MAX-ACCESS  read-only
    STATUS      current
    DESCRIPTION
            "The amount traffic measured in bytes handled in the
             current SA in the outbound direction."
    ::= { ipsecIkeSaEntry 20 }

ipsecIkeSaTotalSaNum OBJECT-TYPE
    SYNTAX      Counter32
    MAX-ACCESS  read-only
    STATUS      current
    DESCRIPTION
            "The total number of SAs, including the current SA,
             that have been set up to support this virtual tunnel."
    ::= { ipsecIkeSaEntry 21 }

ipsecIkeSaTotalTime OBJECT-TYPE
    SYNTAX      Counter32
    MAX-ACCESS  read-only
    STATUS      current
    DESCRIPTION
            "The total time in minutes that this virtual tunnel
             has been up.

             If this is a permanent virtual tunnel, it is reset to
             zero when the tunnel goes to the link-up state."
    ::= { ipsecIkeSaEntry 22 }

ipsecIkeSaTotalInboundTraffic OBJECT-TYPE
    SYNTAX      Counter64
    MAX-ACCESS  read-only
    STATUS      current
    DESCRIPTION
            "The total amount of traffic measured in bytes handled
             in the tunnel in the inbound direction. In other
             words, it is the aggregate value of all inbound
             traffic carried by all SAs ever set up to support the
             virtual tunnel.

             If this is a permanent virtual tunnel, it is not reset
             to zero when the tunnel goes to the link-up state."
    ::= { ipsecIkeSaEntry 23 }

ipsecIkeSaTotalOutboundTraffic OBJECT-TYPE
    SYNTAX      Counter64
    MAX-ACCESS  read-only
    STATUS      current
    DESCRIPTION
            "The total amount of traffic measured in bytes handled
             in the tunnel in the outbound direction. In other
             words, it is the aggregate value of all inbound
             traffic carried by all SAs ever set up to support the
             virtual tunnel.

             If this is a permanent virtual tunnel, it is not reset
             to zero when the tunnel goes to the link-up state."
    ::= { ipsecIkeSaEntry 24 }

ipsecIkeSaDecryptErrors OBJECT-TYPE
    SYNTAX      Counter32
    MAX-ACCESS  read-only
    STATUS      current
    DESCRIPTION
            "The total number of inbound packets to this SA
             discarded due to decryption errors.

             Note that this refers to IKE protocol packets, and not
             to packets carried by SAs set up by the SAs supporting
             this tunnel.

             If this is a permanent virtual tunnel, it is not reset
             to zero when the tunnel goes to the link-up state."
    ::= { ipsecIkeSaEntry 25 }

ipsecIkeSaHashErrors OBJECT-TYPE
    SYNTAX      Counter32
    MAX-ACCESS  read-only
    STATUS      current
    DESCRIPTION
            "The total number of inbound packets to this SA
             discarded due to hash errors.

             Note that this refers to IKE protocol packets, and not
             to packets carried by SAs set up by the SAs supporting
             this tunnel.

             If this is a permanent virtual tunnel, it is not reset
             to zero when the tunnel goes to the link-up state."
    ::= { ipsecIkeSaEntry 26 }


ipsecIkeSaIpsecInboundTraffic OBJECT-TYPE
    SYNTAX      Counter64
    MAX-ACCESS  read-only
    STATUS      current
    DESCRIPTION
            "The total amount of inbound traffic measured in bytes
             handled by all protocol SAs set up by phase 1 SAs
             supporting this tunnel.

             If this is a permanent virtual tunnel, it is not reset
             to zero when the tunnel goes to the link-up state."
    ::= { ipsecIkeSaEntry 27 }

ipsecIkeSaIpsecOutboundTraffic OBJECT-TYPE
    SYNTAX      Counter64
    MAX-ACCESS  read-only
    STATUS      current
    DESCRIPTION
            "The total amount of outbound traffic measured in bytes
             handled by all protocol SAs set up by phase 1 SAs
             supporting this tunnel.

             If this is a permanent virtual tunnel, it is not reset
             to zero when the tunnel goes to the link-up state."
    ::= { ipsecIkeSaEntry 28 }

ipsecIkeSaIpsecDecryptErrors OBJECT-TYPE
    SYNTAX      Counter32
    MAX-ACCESS  read-only
    STATUS      current
    DESCRIPTION
            "The total number of inbound packets discarded by all
             protocol SAs due to decryption errors.

             If this is a permanent virtual tunnel, it is not reset
             to zero when the tunnel goes to the link-up state."
    ::= { ipsecIkeSaEntry 29 }

ipsecIkeSaIpsecAuthErrors OBJECT-TYPE
    SYNTAX      Counter32
    MAX-ACCESS  read-only
    STATUS      current
    DESCRIPTION
            "The total number of inbound packets discarded by all
             protocol SAs due to authentication errors. This
             includes hash failures in IPSec SAs using ESP and AH.

             If this is a permanent virtual tunnel, it is not reset
             to zero when the tunnel goes to the link-up state."
    ::= { ipsecIkeSaEntry 30 }

ipsecIkeSaIpsecReplayErrors OBJECT-TYPE
    SYNTAX      Counter32
    MAX-ACCESS  read-only
    STATUS      current
    DESCRIPTION
            "The total number of inbound packets discarded by all
             protocol SAs due to replay errors.

             If this is a permanent virtual tunnel, it is not reset
             to zero when the tunnel goes to the link-up state."
--  ::= { ipsecIkeSaEntry 30 }
    ::= { ipsecIkeSaEntry 31 }


-- the IPSec Tunnel MIB-Group
--
-- a collection of objects providing information about
-- IPSec SA-based Tunnels


ipsecTunnelIfTable OBJECT-TYPE
    SYNTAX     SEQUENCE OF ipsecTunnelIfEntry
    MAX-ACCESS not-accessible
    STATUS     current
    DESCRIPTION
            "The (conceptual) table containing information on IPSec
             SA-based tunnels."
    ::= { ipsec 2 }

ipsecTunnelIfEntry OBJECT-TYPE
    SYNTAX     IpsecTunnelIfEntry
    MAX-ACCESS not-accessible
    STATUS     current
    DESCRIPTION
            "An entry (conceptual row) containing the information
             on a particular configured tunnel."
    INDEX      { ipsecTunnelIfIndex }
    ::= { ipsecTunnelIfTable 1 }

IpsecTunnelIfEntry ::= SEQUENCE {
   ipsecTunnelIfIndex      Integer32,
   ipsecTunnelIkeSa        Integer32, -- if not static
   ipsecTunnelType         INTEGER, -- static, transient, permanent

-- tunnel identifiers
   ipsecTunnelIfLocalAddressOrStart          IpAddress,
   ipsecTunnelIfLocalAddressMaskOrEnd        IpAddress,
   ipsecTunnelIfRemoteAddressOrStart         IpAddress,
   ipsecTunnelIfRemoteAddressMaskOrEnd       IpAddress,
   ipsecTunnelIfProtocol                     Integer32,
   ipsecTunnelIfLocalPort                    Integer32,
   ipsecTunnelIfRemotePort                   Integer32,

-- tunnel security
   ipsecTunnelMode                  INTEGER,
   ipsecTunnelEspEncAlg             Integer32,
   ipsecTunnelEspEncLeyLength       Integer32,
   ipsecTunnelEspAuthAlg            Integer32,
   ipsecTunnelAhAuthAlg             Integer32,
   ipsecTunnelCompAlg               Integer32

-- aggregate statistics
   ipsecTunnelCurrentSaNum          Counter32
   ipsecTunnelTotalSaNum            Counter32
   ipsecTunnelTotalTimeUp           Counter32,
   ipsecTunnelTotalInboundTraffic   Counter64,
   ipsecTunnelTotalOutboundTraffic  Counter64,

-- aggregate error statistics
   ipsecTunnelDecryptErrors         Counter32,
   ipsecTunnelAuthErrors            Counter32,
   ipsecTunnelReplayErrors          Counter32,


}


ipsecTunnelIfIndex OBJECT-TYPE
    SYNTAX      Integer32 (1..2147483647)
    MAX-ACCESS  read-only
    STATUS      current
    DESCRIPTION
            "A unique value, greater than zero, for each tunnel
             interface.  It is recommended that values are assigned
             contiguously starting from 1.

             The value for each tunnel interface must remain
             constant at least from one re-initialization of the
             entity's network management system to the next
             re-initialization.

             Further, the value for tunnel interfaces that are
             marked as permanent must remain constant across all
             re-initializations of the network management system."
    ::= { ipsecTunnelIfEntry 1 }

ipsecTunnelIkeSa OBJECT-TYPE
    SYNTAX      Integer32 (0..2147483647)
    MAX-ACCESS  read-only
    STATUS      current
    DESCRIPTION
            "The value of the index into the IKE SA tunnel table
             that created this tunnel (ipsecIkeSaIndex), or 0 if
             the tunnel is created by a static IPSec SA."
    ::= { ipsecTunnelIfEntry 2 }

ipsecTunnelType OBJECT-TYPE
    SYNTAX      INTEGER { static(0), transient(1), permanent(2) }
    MAX-ACCESS  read-only
    STATUS      current
    DESCRIPTION
            "The type of the virtual tunnel represented by this
             row.

             static means that the tunnel is supported by a single
             static IPSec SA that was setup by configuration, and
             not by using a key exchange protocol. In this case,
             the value of ipsecTunnelIkeSa must be 0."
    ::= { ipsecTunnelIfEntry 3 }

ipsecTunnelIfLocalAddressOrStart OBJECT-TYPE
    SYNTAX     IpAddress
    MAX-ACCESS read-only
    STATUS     current
    DESCRIPTION
            "The address of or the start address (if an address
             range) of the local endpoint of the tunnel, or 0.0.0.0
             if unknown or transport mode."
    ::= { ipsecTunnelIfTable 4 }

ipsecTunnelIfLocalAddressMaskOrEnd OBJECT-TYPE
    SYNTAX     IpAddress
    MAX-ACCESS read-only
    STATUS     current
    DESCRIPTION
            "The mask of or the end address (if an address
             range) of the local endpoint of the tunnel, or 0.0.0.0
             if unknown or transport mode."
    ::= { ipsecTunnelIfTable 5 }

ipsecTunnelIfRemoteAddressOrStart OBJECT-TYPE
    SYNTAX     IpAddress
    MAX-ACCESS read-only
    STATUS     current
    DESCRIPTION
            "The address of or the start address (if an address
             range) of the remote endpoint of the tunnel,
             or 0.0.0.0 if unknown or transport mode."
    ::= { ipsecTunnelIfTable 6 }

ipsecTunnelIfRemoteAddressMaskOrEnd OBJECT-TYPE
    SYNTAX     IpAddress
    MAX-ACCESS read-only
    STATUS     current
    DESCRIPTION
            "The mask of or the end address (if an address
             range) of the remote endpoint of the tunnel,
             or 0.0.0.0 if unknown or transport mode."
    ::= { ipsecTunnelIfTable 7 }

ipsecTunnelIfProtocol OBJECT-TYPE
    SYNTAX     Integer32
    MAX-ACCESS read-only
    STATUS     current
    DESCRIPTION
            "The number of the protocol that this tunnel carries,
             or 0 if it carries any protocol."
    ::= { ipsecTunnelIfTable 8 }

ipsecTunnelIfLocalPort OBJECT-TYPE
    SYNTAX     Integer32
    MAX-ACCESS read-only
    STATUS     current
    DESCRIPTION
            "The number of the local port that this tunnel carries,
             or 0 if it carries any port number."
    ::= { ipsecTunnelIfTable 9 }

ipsecTunnelIfRemotePort OBJECT-TYPE
    SYNTAX     Integer32
    MAX-ACCESS read-only
    STATUS     current
    DESCRIPTION
            "The number of the remote port that this tunnel
             carries, or 0 if it carries any port number."
    ::= { ipsecTunnelIfTable 10 }

ipsecTunnelMode OBJECT-TYPE
    SYNTAX     INTEGER { transport(1), tunnel(2) }
    MAX-ACCESS read-only
    STATUS     current
    DESCRIPTION
            "The type of encapulation used by this tunnel."
    ::= { ipsecTunnelIfTable 11 }

ipsecTunnelEspEncAlg OBJECT-TYPE
    SYNTAX      INTEGER
    MAX-ACCESS  read-only
    STATUS      current
    DESCRIPTION
            "A unique value representing the encryption algorithm
             applied to traffic carried by this SA if it uses ESP
             or 0 if there is no encryption applied by ESP
             or if ESP is not used.

             Specific values are taken from section 4.4.4
             of [IPDOI]."
    ::= { ipsecTunnelIfTable 12 }

ipsecTunnelEspEncLeyLength OBJECT-TYPE
    SYNTAX      Integer32
    MAX-ACCESS  read-only
    STATUS      current
    DESCRIPTION
            "The length of the encryption key in bits used for the
             algorithm specified in the ipsecTunnelEspEncAlg
             object, or 0 if the key length is implicit in the
             specified algorithm or there is no encryption
             specified."
    ::= { ipsecTunnelIfTable 13 }

ipsecTunnelEspAuthAlg OBJECT-TYPE
    SYNTAX      Integer32
    MAX-ACCESS  read-only
    STATUS      current
    DESCRIPTION
            "A unique value representing the hash algorithm
             applied to traffic carried by this SA if it uses ESP
             or 0 if there is no authentication applied by ESP
             or if ESP is not used.

             Specific values are taken from the Authentication
             Algorithm attribute values of Section 4.5 of [IPDOI]."
    ::= { ipsecTunnelIfTable 14 }

ipsecTunnelAhAuthAlg OBJECT-TYPE
    SYNTAX      Integer32
    MAX-ACCESS  read-only
    STATUS      current
    DESCRIPTION
            "A unique value representing the hash algorithm
             applied to traffic carried by this SA if it uses AH
             or 0 if AH is not used.

             Specific values are taken from Section 4.4.3 of [IPDOI]."
    ::= { ipsecTunnelIfTable 15 }

ipsecTunnelCompAlg OBJECT-TYPE
    SYNTAX      Integer32
    MAX-ACCESS  read-only
    STATUS      current
    DESCRIPTION
            "A unique value representing the compression algorithm
             applied to traffic carried by this SA if it uses
             IPCOMP.

             Specific values are taken from Section 4.4.5
             of [IPDOI]."
    ::= { ipsecTunnelIfTable 16 }

ipsecTunnelCurrentSaNum OBJECT-TYPE
    SYNTAX      Gauge32
    MAX-ACCESS  read-only
    STATUS      current
    DESCRIPTION
            "The number of current SAs set up to support this
             virtual tunnel."
    ::= { ipsecTunnelIfTable 17 }

ipsecTunnelTotalSaNum OBJECT-TYPE
    SYNTAX      Counter32
    MAX-ACCESS  read-only
    STATUS      current
    DESCRIPTION
            "The total number of SAs, including all current SAs,
             that have been set up to support this virtual tunnel."
    ::= { ipsecTunnelIfTable 18 }

ipsecTunnelTotalTimeUp OBJECT-TYPE
    SYNTAX      Counter32
    MAX-ACCESS  read-only
    STATUS      current
    DESCRIPTION
            "The total time in minutes that this virtual tunnel
             has been up.

             If this is a permanent virtual tunnel, it is reset to
             zero when the number of current SAs
             (ipsecTunnelCurrentSaNum) changes from 0 to 1."
    ::= { ipsecTunnelIfTable 19 }

ipsecTunnelTotalInboundTraffic OBJECT-TYPE
    SYNTAX      Counter64
    MAX-ACCESS  read-only
    STATUS      current
    DESCRIPTION
            "The total amount of traffic measured in bytes handled
             in the tunnel in the inbound direction. In other
             words, it is the aggregate value of all inbound
             traffic carried by all protocol SAs ever set up to
             support the virtual tunnel.

             If this is a permanent virtual tunnel, it is not reset
             to zero when the number of current SAs
             (ipsecTunnelCurrentSaNum) changes from 0 to 1."
    ::= { ipsecTunnelIfTable 20 }

ipsecTunnelTotalOutboundTraffic OBJECT-TYPE
    SYNTAX      Counter64
    MAX-ACCESS  read-only
    STATUS      current
    DESCRIPTION
            "The total amount of traffic measured in bytes handled
             in the tunnel in the outbound direction. In other
             words, it is the aggregate value of all inbound
             traffic carried by all protocol SAs ever set up to
             support the virtual tunnel.

             If this is a permanent virtual tunnel, it is not reset
             to zero when the number of current SAs
             (ipsecTunnelCurrentSaNum) changes from 0 to 1."
    ::= { ipsecTunnelIfTable 21 }

ipsecTunnelDecryptErrors OBJECT-TYPE
    SYNTAX      Counter32
    MAX-ACCESS  read-only
    STATUS      current
    DESCRIPTION
            "The total number of inbound packets discarded by this
             virtual tunnel due to decryption errors in ESP.

             If this is a permanent virtual tunnel, it is not reset
             to zero when the number of current SAs
             (ipsecTunnelCurrentSaNum) changes from 0 to 1."
    ::= { ipsecTunnelIfTable 22 }

ipsecTunnelAuthErrors OBJECT-TYPE
    SYNTAX      Counter32
    MAX-ACCESS  read-only
    STATUS      current
    DESCRIPTION
            "The total number of inbound packets discarded by this
             virtual tunnel due to authentication errors. This
             includes hash failures in IPSec SA bundles using both
             ESP and AH.

             If this is a permanent virtual tunnel, it is not reset
             to zero when the number of current SAs
             (ipsecTunnelCurrentSaNum) changes from 0 to 1."
--  ::= { ipsecTunnelIfTable 30 }
    ::= { ipsecTunnelIfTable 23 }

ipsecTunnelReplayErrors OBJECT-TYPE
    SYNTAX      Counter32
    MAX-ACCESS  read-only
    STATUS      current
    DESCRIPTION
            "The total number of inbound packets discarded by this
             virtual tunnel due to replay errors. This includes
             replay failures in IPSec SA bundles using both ESP and
             AH.

             If this is a permanent virtual tunnel, it is not reset
             to zero when the number of current SAs
             (ipsecTunnelCurrentSaNum) changes from 0 to 1."
--  ::= { ipsecTunnelIfTable 30 }
    ::= { ipsecTunnelIfTable 24 }


-- the IPSec SA MIB-Group
--
-- a collection of objects providing information about
-- IPSec SAs


ipsecSaTable OBJECT-TYPE
    SYNTAX     SEQUENCE OF IpsecSaEntry
    MAX-ACCESS not-accessible
    STATUS     current
    DESCRIPTION
            "The (conceptual) table containing information on
             IPSec SAs."
    ::= { ipsec 3 }

ipsecSaEntry OBJECT-TYPE
    SYNTAX     IpsecSaEntry
    MAX-ACCESS not-accessible
    STATUS     current
    DESCRIPTION
            "An entry (conceptual row) containing the information
             on a particular IPSec SA."
    INDEX      { ipsecSaIndex }
    ::= { ipsecSaTable 1 }

IpsecSaEntry ::= SEQUENCE {
   ipsecSaIndex        Integer32,
   ipsecSaTunnel       Integer32,  -- index from ipsecTunnelIfTable

-- expiration limits
   ipsecSaCreationTime           DateAndTime,
   ipsecSaTimeLimit              Counter32,  -- seconds, 0 if none
   ipsecSaTrafficLimit           Counter64,  -- bytes, 0 if none

-- current operating statistics
   ipsecSaInboundTraffic         Counter64,
   ipsecSaOutboundTraffic        Counter64,


-- error statistics
   ipsecSaDecryptErrors          Counter32,
   ipsecSaAuthErrors             Counter32,
   ipsecSaReplayErrors           Counter32,
}


ipsecSaIndex OBJECT-TYPE
    SYNTAX      Integer32 (1..2147483647)
    MAX-ACCESS  read-only
    STATUS      current
    DESCRIPTION
            "A unique value, greater than zero, for each IPSec SA.
             It is recommended that values are assigned
             contiguously starting from 1."
    ::= { ipsecSaEntry 1 }

ipsecSaTunnel OBJECT-TYPE
    SYNTAX      Integer32 (1..2147483647)
    MAX-ACCESS  read-only
    STATUS      current
    DESCRIPTION
            "The value of the index into the IPSec SA tunnel table
             that this SA supports (ipsecTunnelIfIndex)."
    ::= { ipsecSaEntry 2 }

ipsecSaCreationTime OBJECT-TYPE
    SYNTAX      DateAndTime
    MAX-ACCESS  read-only
    STATUS      current
    DESCRIPTION
            "The date and time that the current SA was set up."
    ::= { ipsecSaEntry 3 }

ipsecSaTimeLimit OBJECT-TYPE
    SYNTAX      Counter32
    MAX-ACCESS  read-only
    STATUS      current
    DESCRIPTION
            "The maximum lifetime in seconds of the SA,
             or 0 if there is no time constraint on its expiration."
    ::= { ipsecSaEntry 4 }

ipsecSaTrafficLimit OBJECT-TYPE
    SYNTAX      Counter32
    MAX-ACCESS  read-only
    STATUS      current
    DESCRIPTION
            "The maximum traffic in 1024-byte blocks that the
             SA is allowed to support,
             or 0 if there is no traffic constraint on its
             expiration."
    ::= { ipsecSaEntry 5 }

ipsecSaInboundTraffic OBJECT-TYPE
    SYNTAX      Counter64
    MAX-ACCESS  read-only
    STATUS      current
    DESCRIPTION
            "The amount traffic measured in bytes handled in the
             SA in the inbound direction."
    ::= { ipsecSaEntry 6 }

ipsecSaOutboundTraffic OBJECT-TYPE
    SYNTAX      Counter64
    MAX-ACCESS  read-only
    STATUS      current
    DESCRIPTION
            "The amount traffic measured in bytes handled in the
             SA in the outbound direction."
    ::= { ipsecSaEntry 7 }

ipsecSaDecryptErrors OBJECT-TYPE
    SYNTAX      Counter32
    MAX-ACCESS  read-only
    STATUS      current
    DESCRIPTION
            "The number of inbound packets discarded by the SA
             due to decryption errors."
    ::= { ipsecSaEntry 8 }

ipsecSaAuthErrors OBJECT-TYPE
    SYNTAX      Counter32
    MAX-ACCESS  read-only
    STATUS      current
    DESCRIPTION
            "The number of inbound packets discarded by the SA
             due to authentication errors. This includes
             hash failures in both ESP and AH."
    ::= { ipsecSaEntry 9 }

ipsecSaReplayErrors OBJECT-TYPE
    SYNTAX      Counter32
    MAX-ACCESS  read-only
    STATUS      current
    DESCRIPTION
            "The number of inbound packets discarded by the SA
             due to replay errors. This includes replay failures
             both ESP and AH."
    ::= { ipsecSaEntry 10 }

END
