TLSTM-MIB DEFINITIONS ::= BEGIN

IMPORTS
    MODULE-IDENTITY, OBJECT-TYPE,
    OBJECT-IDENTITY, snmpModules, snmpDomains,
    Counter32, Unsigned32, NOTIFICATION-TYPE
      FROM SNMPv2-SMI
    TEXTUAL-CONVENTION, TimeStamp, RowStatus, StorageType,
    AutonomousType
      FROM SNMPv2-TC
    MODULE-COMPLIANCE, OBJECT-GROUP, NOTIFICATION-GROUP
      FROM SNMPv2-CONF
    SnmpAdminString
      FROM SNMP-FRAMEWORK-MIB
    snmpTargetParamsName, snmpTargetAddrName
      FROM SNMP-TARGET-MIB
    ;

tlstmMIB MODULE-IDENTITY
    LAST-UPDATED "201003060000Z"
    ORGANIZATION "ISMS Working Group"
    CONTACT-INFO "WG-EMail:   isms@lists.ietf.org
                  Subscribe:  isms-request@lists.ietf.org

                  Chairs:
                     Juergen Schoenwaelder
                     Jacobs University Bremen
                     Campus Ring 1
                     28725 Bremen
                     Germany
                     +49 421 200-3587
                     j.schoenwaelder@jacobs-university.de

                     Russ Mundy
                     SPARTA, Inc.
                     7110 Samuel Morse Drive
                     Columbia, MD  21046
                     USA

                  Co-editors:
                     Wes Hardaker
                     Sparta, Inc.



                     P.O. Box 382
                     Davis, CA  95617
                     USA
                     ietf@hardakers.net
                  "

    DESCRIPTION  "
        The TLS Transport Model MIB

        Copyright (c) 2010 IETF Trust and the persons identified as
        the document authors.  All rights reserved.

        Redistribution and use in source and binary forms, with or
        without modification, is permitted pursuant to, and subject
        to the license terms contained in, the Simplified BSD License
        set forth in Section 4.c of the IETF Trust's Legal Provisions
        Relating to IETF Documents
        (http://trustee.ietf.org/license-info).

        This version of this MIB module is part of RFC XXXX;
        see the RFC itself for full legal notices."

-- NOTE to RFC editor: replace XXXX with actual RFC number
--                     for this document and remove this note

       REVISION     "201003060000Z"
       DESCRIPTION  "The initial version, published in RFC XXXX."
-- NOTE to RFC editor: replace XXXX with actual RFC number
--                     for this document and remove this note

    ::= { snmpModules 42 }
-- RFC Ed.: replace xxxx with IANA-assigned number and
--          remove this note

-- ************************************************
-- subtrees of the TLSTM-MIB
-- ************************************************

tlstmNotifications OBJECT IDENTIFIER ::= { tlstmMIB 0 }
tlstmIdentities    OBJECT IDENTIFIER ::= { tlstmMIB 1 }
tlstmObjects       OBJECT IDENTIFIER ::= { tlstmMIB 2 }
tlstmConformance   OBJECT IDENTIFIER ::= { tlstmMIB 3 }

-- ************************************************
-- tlstmObjects - Objects
-- ************************************************

snmpTLSTCPDomain OBJECT-IDENTITY



    STATUS      current
    DESCRIPTION
        "The SNMP over TLS transport domain.  The corresponding
        transport address is of type SnmpTLSAddress.

        The securityName prefix to be associated with the
        snmpTLSTCPDomain is 'tls'.  This prefix may be used by
        security models or other components to identify which secure
        transport infrastructure authenticated a securityName."

    ::= { snmpDomains 142 }


-- RFC Ed.: replace xx with IANA-assigned number and
--          remove this note

-- RFC Ed.: replace 'tls' with the actual IANA assigned prefix string
--          if 'tls' is not assigned to this document.

snmpDTLSUDPDomain OBJECT-IDENTITY
    STATUS      current
    DESCRIPTION
        "The SNMP over DTLS/UDP transport domain.  The corresponding
        transport address is of type SnmpTLSAddress.

        The securityName prefix to be associated with the
        snmpDTLSUDPDomain is 'dudp'.  This prefix may be used by
        security models or other components to identify which secure
        transport infrastructure authenticated a securityName."

    ::= { snmpDomains 143 }


-- RFC Ed.: replace yy with IANA-assigned number and
--          remove this note

-- RFC Ed.: replace 'dudp' with the actual IANA assigned prefix string
--          if 'dudp' is not assigned to this document.

SnmpTLSAddress ::= TEXTUAL-CONVENTION
    DISPLAY-HINT "1a"
    STATUS       current
    DESCRIPTION
        "Represents a IPv4 address, an IPv6 address or an US-ASCII
        encoded hostname and port number.

        An IPv4 address must be in dotted decimal format followed by a
        colon ':' (US-ASCII character 0x3A) and a decimal port number



        in US-ASCII.

        An IPv6 address must be a colon separated format, surrounded
        by square brackets ('[', US-ASCII character 0x5B, and ']',
        US-ASCII character 0x5D), followed by a colon ':' (US-ASCII
        character 0x3A) and a decimal port number in US-ASCII.

        A hostname is always in US-ASCII (as per RFC1033);
        internationalized hostnames are encoded in US-ASCII as
        specified in RFC 3490.  The hostname is followed by a colon
        ':' (US-ASCII character 0x3A) and a decimal port number in
        US-ASCII.  The name SHOULD be fully qualified whenever
        possible.

        Values of this textual convention may not be directly usable
        as transport-layer addressing information, and may require
        run-time resolution.  As such, applications that write them
        must be prepared for handling errors if such values are not
        supported, or cannot be resolved (if resolution occurs at the
        time of the management operation).

        The DESCRIPTION clause of TransportAddress objects that may
        have SnmpTLSAddress values must fully describe how (and
        when) such names are to be resolved to IP addresses and vice
        versa.

        This textual convention SHOULD NOT be used directly in object
        definitions since it restricts addresses to a specific
        format.  However, if it is used, it MAY be used either on its
        own or in conjunction with TransportAddressType or
        TransportDomain as a pair.

        When this textual convention is used as a syntax of an index
        object, there may be issues with the limit of 128
        sub-identifiers specified in SMIv2 (STD 58).  It is RECOMMENDED
        that all MIB documents using this textual convention make
        explicit any limitations on index component lengths that
        management software must observe.  This may be done either by
        including SIZE constraints on the index components or by
        specifying applicable constraints in the conceptual row
        DESCRIPTION clause or in the surrounding documentation."
    REFERENCE
      "RFC 1033: DOMAIN ADMINISTRATORS OPERATIONS GUIDE
       RFC 3490: Internationalizing Domain Names in Applications
       RFC 3986: Uniform Resource Identifier (URI): Generic Syntax
       RFC 5246: The Transport Layer Security (TLS) Protocol Version 1.2
      "
    SYNTAX       OCTET STRING (SIZE (1..255))



Fingerprint ::= TEXTUAL-CONVENTION
    DISPLAY-HINT "1x:254x"
    STATUS       current
    DESCRIPTION
       "A Fingerprint value that can be used to uniquely reference
       other data of potentially arbitrary length.

       A Fingerprint value is composed of a 1-octet hashing algorithm
       identifier followed by the fingerprint value.  The octet value
       encoded is taken from the IANA TLS HashAlgorithm Registry
       (RFC5246).  The remaining octets are filled using the results
       of the hashing algorithm.

       This TEXTUAL-CONVENTION allows for a zero-length (blank)
       Fingerprint value for use in tables where the fingerprint value
       may be optional.  MIB definitions or implementations may refuse
       to accept a zero-length value as appropriate."
    REFERENCE
      "RFC 5246: The Transport Layer Security (TLS) Protocol Version 1.2
       http://www.iana.org/assignments/tls-parameters/
      "
    SYNTAX       OCTET STRING (SIZE (0..255))

-- Identities for use in the tlstmCertToTSNTable

tlstmCertToTSNMIdentities    OBJECT IDENTIFIER ::= { tlstmIdentities 1 }

tlstmCertSpecified OBJECT-IDENTITY
    STATUS        current
    DESCRIPTION  "Directly specifies the tmSecurityName to be used for
                  this certificate.  The value of the tmSecurityName
                  to use is specified in the tlstmCertToTSNData
                  column.  The tlstmCertToTSNData column must contain
                  a non-zero length SnmpAdminString compliant value or
                  the mapping described in this row must be considered
                  a failure."
    ::= { tlstmCertToTSNMIdentities 1 }

tlstmCertSANRFC822Name OBJECT-IDENTITY
    STATUS        current
    DESCRIPTION  "Maps a subjectAltName's rfc822Name to a
                  tmSecurityName.  The local part of the rfc822Name is
                  passed unaltered but the host-part of the name must
                  be passed in lower case.

                  Example rfc822Name Field:  FooBar@Example.COM
                  is mapped to tmSecurityName: FooBar@example.com"
    ::= { tlstmCertToTSNMIdentities 2 }



tlstmCertSANDNSName OBJECT-IDENTITY
    STATUS        current
    DESCRIPTION  "Maps a subjectAltName's dNSName to a
                  tmSecurityName after first converting it to all
                  lower case."
    ::= { tlstmCertToTSNMIdentities 3 }

tlstmCertSANIpAddress OBJECT-IDENTITY
    STATUS        current
    DESCRIPTION  "Maps a subjectAltName's iPAddress to a
                  tmSecurityName by transforming the binary encoded
                  address as follows:


                  1) for IPv4 the value is converted into a decimal
                     dotted quad address (e.g. '192.0.2.1')

                  2) for IPv6 addresses the value is converted into a
                     32-character all lowercase hexadecimal string
                     without any colon separators.

                     Note that the resulting length is the maximum
                     length supported by the View-Based Access Control
                     Model (VACM).  Note that using both the Transport
                     Security Model's support for transport prefixes
                     (see the SNMP-TSM-MIB's
                     snmpTsmConfigurationUsePrefix object for details)
                     will result in securityName lengths that exceed
                     what VACM can handle."
    ::= { tlstmCertToTSNMIdentities 4 }

tlstmCertSANAny OBJECT-IDENTITY
    STATUS        current
    DESCRIPTION  "Maps any of the following fields using the
                  corresponding mapping algorithms:

                  |------------+------------------------|
                  | Type       | Algorithm              |
                  |------------+------------------------|
                  | rfc822Name | tlstmCertSANRFC822Name |
                  | dNSName    | tlstmCertSANDNSName    |
                  | iPAddress  | tlstmCertSANIpAddress  |
                  |------------+------------------------|

                  The first matching subjectAltName value found in the
                  certificate of the above types MUST be used when
                  deriving the tmSecurityName."
    ::= { tlstmCertToTSNMIdentities 5 }



tlstmCertCommonName OBJECT-IDENTITY
    STATUS        current

    DESCRIPTION  "Maps a certificate's CommonName to a tmSecurityName
                  after converting it to a UTF-8 encoding."
    ::= { tlstmCertToTSNMIdentities 6 }

-- The snmpTlstmSession Group

snmpTlstmSession           OBJECT IDENTIFIER ::= { tlstmObjects 1 }

snmpTlstmSessionOpens  OBJECT-TYPE
    SYNTAX       Counter32
    MAX-ACCESS   read-only
    STATUS       current
    DESCRIPTION
       "The number of times an openSession() request has been executed
       as an (D)TLS client, regardless of whether it succeeded or
       failed."
    ::= { snmpTlstmSession 1 }

snmpTlstmSessionClientCloses  OBJECT-TYPE
    SYNTAX       Counter32
    MAX-ACCESS   read-only
    STATUS       current
    DESCRIPTION
        "The number of times a closeSession() request has been
        executed as an (D)TLS client, regardless of whether it
        succeeded or failed."
    ::= { snmpTlstmSession 2 }

snmpTlstmSessionOpenErrors  OBJECT-TYPE
    SYNTAX       Counter32
    MAX-ACCESS   read-only
    STATUS       current
    DESCRIPTION
        "The number of times an openSession() request failed to open a
        session as a (D)TLS client, for any reason."
    ::= { snmpTlstmSession 3 }

snmpTlstmSessionAccepts  OBJECT-TYPE
    SYNTAX       Counter32
    MAX-ACCESS   read-only
    STATUS       current
    DESCRIPTION
       "The number of times a (D)TLS server has accepted a new
       connection from a client and has received at least one SNMP
       message through it."



    ::= { snmpTlstmSession 4 }

snmpTlstmSessionServerCloses  OBJECT-TYPE
    SYNTAX       Counter32
    MAX-ACCESS   read-only
    STATUS       current
    DESCRIPTION
        "The number of times a closeSession() request has been
        executed as an (D)TLS server, regardless of whether it
        succeeded or failed."
    ::= { snmpTlstmSession 5 }

snmpTlstmSessionNoSessions  OBJECT-TYPE
    SYNTAX       Counter32
    MAX-ACCESS   read-only
    STATUS       current
    DESCRIPTION
        "The number of times an outgoing message was dropped because
        the session associated with the passed tmStateReference was no
        longer (or was never) available."
    ::= { snmpTlstmSession 6 }

snmpTlstmSessionInvalidClientCertificates OBJECT-TYPE
    SYNTAX       Counter32
    MAX-ACCESS   read-only
    STATUS       current
    DESCRIPTION
        "The number of times an incoming session was not established
        on an (D)TLS server because the presented client certificate was
        invalid.  Reasons for invalidation include, but are not
        limited to, cryptographic validation failures or lack of a
        suitable mapping row in the tlstmCertToTSNTable."
    ::= { snmpTlstmSession 7 }

snmpTlstmSessionUnknownServerCertificate OBJECT-TYPE
    SYNTAX       Counter32
    MAX-ACCESS   read-only
    STATUS       current
    DESCRIPTION
        "The number of times an outgoing session was not established
         on an (D)TLS client because the server certificate presented
         by a SNMP over (D)TLS server was invalid because no
         configured fingerprint or CA was acceptable to validate it.
         This may result because there was no entry in the
         tlstmAddrTable or because no path could be found to a known
         certification authority."
    ::= { snmpTlstmSession 8 }




snmpTlstmSessionInvalidServerCertificates OBJECT-TYPE
    SYNTAX       Counter32
    MAX-ACCESS   read-only
    STATUS       current
    DESCRIPTION
        "The number of times an outgoing session was not established
         on an (D)TLS client because the server certificate presented
         by an SNMP over (D)TLS server could not be validated even if
         the fingerprint or expected validation path was known.  I.E.,
         a cryptographic validation error occurred during certificate
         validation processing.

        Reasons for invalidation include, but are not
        limited to, cryptographic validation failures."
    ::= { snmpTlstmSession 9 }

snmpTlstmSessionInvalidCaches OBJECT-TYPE
    SYNTAX       Counter32
    MAX-ACCESS   read-only
    STATUS       current
    DESCRIPTION
        "The number of outgoing messages dropped because the
        tmStateReference referred to an invalid cache."
    ::= { snmpTlstmSession 10 }

-- Configuration Objects

tlstmConfig          OBJECT IDENTIFIER ::= { tlstmObjects 2 }

-- Certificate mapping

tlstmCertificateMapping    OBJECT IDENTIFIER ::= { tlstmConfig 1 }

tlstmCertToTSNCount OBJECT-TYPE
    SYNTAX      Unsigned32
    MAX-ACCESS  read-only
    STATUS      current
    DESCRIPTION
        "A count of the number of entries in the tlstmCertToTSNTable"
    ::= { tlstmCertificateMapping 1 }

tlstmCertToTSNTableLastChanged OBJECT-TYPE
    SYNTAX      TimeStamp
    MAX-ACCESS  read-only
    STATUS      current
    DESCRIPTION
        "The value of sysUpTime.0 when the tlstmCertToTSNTable
        was last modified through any means, or 0 if it has not been



        modified since the command responder was started."
    ::= { tlstmCertificateMapping 2 }

tlstmCertToTSNTable OBJECT-TYPE
    SYNTAX      SEQUENCE OF TlstmCertToTSNEntry
    MAX-ACCESS  not-accessible
    STATUS      current
    DESCRIPTION
        "A table listing the fingerprints of X.509 certificates known
        to the entity and the associated method for determining the
        SNMPv3 security name from a certificate.

        On an incoming (D)TLS/SNMP connection the client's presented
        certificate must be examined and validated based on an
        established trusted path from a CA certificate or self-signed
        public certificate (e.g. RFC5280).  This table provides a
        mapping from a validated certificate to a tmSecurityName.
        This table does not provide any mechanisms for uploading
        trusted certificates; the transfer of any needed trusted
        certificates for path validation is expected to occur through
        an out-of-band transfer.

        Once the authenticity of a certificate has been verified, this
        table is consulted to determine the appropriate tmSecurityName
        to identify with the remote connection.  This is done by
        considering each active row from this table in prioritized
        order according to its tlstmCertToTSNID value.  Each row's
        tlstmCertToTSNFingerprint value determines whether the row is a
        match for the incoming connection:

            1) If the row's tlstmCertToTSNFingerprint value identifies
               the presented certificate then consider the row as a
               successful match.

            2) If the row's tlstmCertToTSNFingerprint value identifies
               a locally held copy of a trusted CA certificate and
               that CA certificate was used to validate the path to
               the presented certificate then consider the row as a
               successful match.

        Once a matching row has been found, the tlstmCertToTSNMapType
        value can be used to determine how the tmSecurityName to
        associate with the session should be determined.  See the
        tlstmCertToTSNMapType column's DESCRIPTION for details on
        determining the tmSecurityName value.  If it is impossible to
        determine a tmSecurityName from the row's data combined with the
        data presented in the certificate then additional rows MUST be
        searched looking for another potential match.  If a resulting



        tmSecurityName mapped from a given row is not compatible with
        the needed requirements of a tmSecurityName (e.g., VACM imposes
        a 32-octet-maximum length and the certificate derived
        securityName could be longer) then it must be considered an
        invalid match and additional rows MUST be searched looking for
        another potential match.

        Missing values of tlstmCertToTSNID are acceptable and
        implementations should continue to the next highest numbered
        row.  E.G., the table may legally contain only two rows with
        tlstmCertToTSNID values of 10 and 20.

        Users are encouraged to make use of certificates with
        subjectAltName fields that can be used as tmSecurityNames so
        that a single root CA certificate can allow all child
        certificate's subjectAltName to map directly to a
        tmSecurityName via a 1:1 transformation.  However, this table
        is flexible to allow for situations where existing deployed
        certificate infrastructures do not provide adequate
        subjectAltName values for use as tmSecurityNames.
        Certificates may also be mapped to tmSecurityNames using the
        CommonName portion of the Subject field.  However, the usage
        of the CommonName field is deprecated and thus this usage is
        NOT RECOMMENDED.  Direct mapping from each individual
        certificate fingerprint to a tmSecurityName is also possible
        but requires one entry in the table per tmSecurityName and
        requires more management operations to completely configure a
        device."
    ::= { tlstmCertificateMapping 3 }

tlstmCertToTSNEntry OBJECT-TYPE
    SYNTAX      TlstmCertToTSNEntry
    MAX-ACCESS  not-accessible
    STATUS      current
    DESCRIPTION
        "A row in the tlstmCertToTSNTable that specifies a mapping for
        an incoming (D)TLS certificate to a tmSecurityName to use for a
        connection."
    INDEX   { tlstmCertToTSNID }
    ::= { tlstmCertToTSNTable 1 }

TlstmCertToTSNEntry ::= SEQUENCE {
    tlstmCertToTSNID           Unsigned32,
    tlstmCertToTSNFingerprint  Fingerprint,
    tlstmCertToTSNMapType      AutonomousType,
    tlstmCertToTSNData         OCTET STRING,
    tlstmCertToTSNStorageType  StorageType,
    tlstmCertToTSNRowStatus    RowStatus



}

tlstmCertToTSNID OBJECT-TYPE
    SYNTAX      Unsigned32 (1..4294967295)
    MAX-ACCESS  not-accessible
    STATUS      current
    DESCRIPTION
        "A unique, prioritized index for the given entry.  Lower
        numbers indicate a higher priority."
    ::= { tlstmCertToTSNEntry 1 }

tlstmCertToTSNFingerprint OBJECT-TYPE
    SYNTAX      Fingerprint (SIZE(1..255))
    MAX-ACCESS  read-create
    STATUS      current
    DESCRIPTION
        "A cryptographic hash of a X.509 certificate.  The results of
        a successful matching fingerprint to either the trusted CA in
        the certificate validation path or to the certificate itself
        is dictated by the tlstmCertToTSNMapType column."
    ::= { tlstmCertToTSNEntry 2 }

tlstmCertToTSNMapType OBJECT-TYPE
    SYNTAX      AutonomousType
    MAX-ACCESS  read-create
    STATUS      current
    DESCRIPTION
        "Specifies the mapping type for deriving a tmSecurityName from a
        certificate.  Details for mapping of a particular type SHALL
        be specified in the DESCRIPTION clause of the OBJECT-IDENTITY
        that describes the mapping.  If a mapping succeeds it will
        return a tmSecurityName for use by the TLSTM model and
        processing stops.

        If the resulting mapped value is not compatible with the
        needed requirements of a tmSecurityName (e.g., VACM imposes a
        32-octet-maximum length and the certificate derived
        securityName could be longer) then future rows MUST be
        searched for additional tlstmCertToTSNFingerprint matches to
        look for a mapping that succeeds."
    DEFVAL { tlstmCertSpecified }
    ::= { tlstmCertToTSNEntry 3 }

tlstmCertToTSNData OBJECT-TYPE
    SYNTAX      OCTET STRING (SIZE(0..1024))
    MAX-ACCESS  read-create
    STATUS      current
    DESCRIPTION



        "Auxiliary data used as optional configuration information for
        a given mapping specified by the tlstmCertToTSNMapType column.
        Only some mapping systems will make use of this column.  The
        value in this column MUST be ignored for any mapping type that
        does not require data present in this column."
    DEFVAL { "" }
    ::= { tlstmCertToTSNEntry 4 }

tlstmCertToTSNStorageType OBJECT-TYPE
    SYNTAX       StorageType
    MAX-ACCESS   read-create
    STATUS       current
    DESCRIPTION
        "The storage type for this conceptual row.  Conceptual rows
        having the value 'permanent' need not allow write-access to
        any columnar objects in the row."
    DEFVAL      { nonVolatile }
    ::= { tlstmCertToTSNEntry 5 }

tlstmCertToTSNRowStatus OBJECT-TYPE
    SYNTAX      RowStatus
    MAX-ACCESS  read-create
    STATUS      current
    DESCRIPTION
        "The status of this conceptual row.  This object may be used
        to create or remove rows from this table.

        To create a row in this table, an administrator must set this
        object to either createAndGo(4) or createAndWait(5).

        Until instances of all corresponding columns are appropriately
        configured, the value of the corresponding instance of the
        tlstmParamsRowStatus column is 'notReady'.

        In particular, a newly created row cannot be made active until
        the corresponding tlstmCertToTSNFingerprint,
        tlstmCertToTSNMapType, and tlstmCertToTSNData columns have been
        set.

        The following objects may not be modified while the
        value of this object is active(1):
            - tlstmCertToTSNFingerprint
            - tlstmCertToTSNMapType
            - tlstmCertToTSNData
        An attempt to set these objects while the value of
        tlstmParamsRowStatus is active(1) will result in
        an inconsistentValue error."
    ::= { tlstmCertToTSNEntry 6 }



-- Maps tmSecurityNames to certificates for use by the SNMP-TARGET-MIB

tlstmParamsCount OBJECT-TYPE
    SYNTAX      Unsigned32
    MAX-ACCESS  read-only
    STATUS      current
    DESCRIPTION
        "A count of the number of entries in the tlstmParamsTable"
    ::= { tlstmCertificateMapping 4 }

tlstmParamsTableLastChanged OBJECT-TYPE
    SYNTAX      TimeStamp
    MAX-ACCESS  read-only
    STATUS      current
    DESCRIPTION
        "The value of sysUpTime.0 when the tlstmParamsTable
        was last modified through any means, or 0 if it has not been
        modified since the command responder was started."
    ::= { tlstmCertificateMapping 5 }

tlstmParamsTable OBJECT-TYPE
    SYNTAX      SEQUENCE OF TlstmParamsEntry
    MAX-ACCESS  not-accessible
    STATUS      current
    DESCRIPTION
        "This table is used by a (D)TLS client when a (D)TLS
        connection is being set up using an entry in the
        SNMP-TARGET-MIB.  It extends the SNMP-TARGET-MIB's
        snmpTargetParamsTable with a fingerprint of a certificate to
        use when establishing such a (D)TLS connection."
    ::= { tlstmCertificateMapping 6 }

tlstmParamsEntry OBJECT-TYPE
    SYNTAX      TlstmParamsEntry
    MAX-ACCESS  not-accessible
    STATUS      current
    DESCRIPTION
        "A conceptual row containing a fingerprint hash of a locally
        held certificate for a given snmpTargetParamsEntry.  The
        values in this row should be ignored if the connection that
        needs to be established, as indicated by the SNMP-TARGET-MIB
        infrastructure, is not a certificate and (D)TLS based
        connection.  The connection SHOULD NOT be established if the
        certificate fingerprint stored in this entry does not point to
        a valid locally held certificate or if it points to an unusable
        certificate (such as might happen when the certificate's
        expiration date has been reached)."
    INDEX    { IMPLIED snmpTargetParamsName }



    ::= { tlstmParamsTable 1 }

TlstmParamsEntry ::= SEQUENCE {
    tlstmParamsClientFingerprint Fingerprint,
    tlstmParamsStorageType       StorageType,
    tlstmParamsRowStatus         RowStatus
}

tlstmParamsClientFingerprint OBJECT-TYPE
    SYNTAX      Fingerprint
    MAX-ACCESS  read-create
    STATUS      current
    DESCRIPTION
        "A cryptographic hash of a X.509 certificate.  This object
        should store the hash of a locally held X.509 certificate (and
        the corresponding private key) that should be used when
        initiating a (D)TLS connection as a (D)TLS client."
    ::= { tlstmParamsEntry 1 }

tlstmParamsStorageType OBJECT-TYPE
    SYNTAX       StorageType
    MAX-ACCESS   read-create
    STATUS       current
    DESCRIPTION
        "The storage type for this conceptual row.  Conceptual rows
        having the value 'permanent' need not allow write-access to
        any columnar objects in the row."
    DEFVAL      { nonVolatile }
    ::= { tlstmParamsEntry 2 }


tlstmParamsRowStatus OBJECT-TYPE
    SYNTAX      RowStatus
    MAX-ACCESS  read-create
    STATUS      current
    DESCRIPTION
        "The status of this conceptual row.  This object may be used
        to create or remove rows from this table.

        To create a row in this table, an administrator must set this
        object to either createAndGo(4) or createAndWait(5).

        Until instances of all corresponding columns are appropriately
        configured, the value of the corresponding instance of the
        tlstmParamsRowStatus column is 'notReady'.

        In particular, a newly created row cannot be made active until
        the corresponding tlstmParamsClientFingerprint column has



        been set.

        The tlstmParamsClientFingerprint object may not be modified
        while the value of this object is active(1).

        An attempt to set these objects while the value of
        tlstmParamsRowStatus is active(1) will result in
        an inconsistentValue error."
    ::= { tlstmParamsEntry 3 }

tlstmAddrCount OBJECT-TYPE
    SYNTAX      Unsigned32
    MAX-ACCESS  read-only
    STATUS      current
    DESCRIPTION
        "A count of the number of entries in the tlstmAddrTable"
    ::= { tlstmCertificateMapping 7 }

tlstmAddrTableLastChanged OBJECT-TYPE
    SYNTAX      TimeStamp
    MAX-ACCESS  read-only
    STATUS      current
    DESCRIPTION
        "The value of sysUpTime.0 when the tlstmAddrTable
        was last modified through any means, or 0 if it has not been
        modified since the command responder was started."
    ::= { tlstmCertificateMapping 8 }

tlstmAddrTable OBJECT-TYPE
    SYNTAX      SEQUENCE OF TlstmAddrEntry
    MAX-ACCESS  not-accessible
    STATUS      current
    DESCRIPTION
        "This table is used by a (D)TLS client when a (D)TLS
          connection is being set up using an entry in the
          SNMP-TARGET-MIB.  It extends the SNMP-TARGET-MIB's
          snmpTargetAddrTable so that the client can verify that the
          correct server has been reached.  This verification can use
          either a certificate fingerprint, or an identity
          authenticated via certification path validation.

          If there is an active row in this table corresponding to the
          entry in the SNMP-TARGET-MIB that was used to establish the
          connection, and the row's tlstmAddrServerFingerprint column
          has non-empty value, then the server's presented certificate
          is compared with the tlstmAddrServerFingerprint value (and
          the tlstmAddrServerIdentity column is ignored).  If the
          fingerprint matches, the verification has succeeded.  If the



          fingerprint does not match then the connection MUST be
          closed.

          If the server's presented certificate has passed
          certification path validation [RFC5280] to a configured
          trust anchor, and an active row exists with a zero-length
          tlstmAddrServerFingerprint value, then the
          tlstmAddrServerIdentity column contains the expected host
          name.  This expected host name is then compared against the
          server's certificate as follows:

            - Implementations MUST support matching the expected host
            name against a dNSName in the subjectAltName extension field
            and SHOULD support checking the name against the common name
            portion of the subject distinguished name.

            - The '*' (ASCII 0x2a) wildcard character is allowed in the
            dNSName of the subjectAltName extension (and in common name,
            if used to store the host name), but only as the left-most
            (least significant) DNS label in that value.  This wildcard
            matches any left-most DNS label in the server name.  That
            is, the subject *.example.com matches the server names
            a.example.com and b.example.com, but does not match
            example.com or a.b.example.com.  Implementations MUST
            support wildcards in certificates as specified above, but
            MAY provide a configuration option to disable them.

            - If the locally configured name is an internationalized
            domain name, conforming implementations MUST convert it to
            the ASCII Compatible Encoding (ACE) format for performing
            comparisons, as specified in Section 7 of [RFC5280].

          If the expected host name fails these conditions then the
          connection MUST be closed.

          If there is no row in this table corresponding to the entry
          in the SNMP-TARGET-MIB and the server can be authorized by
          another, implementation dependent means, then the connection
          MAY still proceed."

    ::= { tlstmCertificateMapping 9 }

tlstmAddrEntry OBJECT-TYPE
    SYNTAX      TlstmAddrEntry
    MAX-ACCESS  not-accessible
    STATUS      current
    DESCRIPTION
        "A conceptual row containing a copy of a certificate's



        fingerprint for a given snmpTargetAddrEntry.  The values in
        this row should be ignored if the connection that needs to be
        established, as indicated by the SNMP-TARGET-MIB
        infrastructure, is not a (D)TLS based connection.  If an
        tlstmAddrEntry exists for a given snmpTargetAddrEntry then the
        presented server certificate MUST match or the connection MUST
        NOT be established.  If a row in this table does not exist to
        match a snmpTargetAddrEntry row then the connection SHOULD
        still proceed if some other certificate validation path
        algorithm (e.g. RFC5280) can be used."
    INDEX    { IMPLIED snmpTargetAddrName }
    ::= { tlstmAddrTable 1 }

TlstmAddrEntry ::= SEQUENCE {
    tlstmAddrServerFingerprint    Fingerprint,
    tlstmAddrServerIdentity       SnmpAdminString,
    tlstmAddrStorageType          StorageType,
    tlstmAddrRowStatus            RowStatus
}

tlstmAddrServerFingerprint OBJECT-TYPE
    SYNTAX      Fingerprint
    MAX-ACCESS  read-create
    STATUS      current
    DESCRIPTION
        "A cryptographic hash of a public X.509 certificate.  This
        object should store the hash of the public X.509 certificate
        that the remote server should present during the (D)TLS
        connection setup.  The fingerprint of the presented
        certificate and this hash value MUST match exactly or the
        connection MUST NOT be established."
    DEFVAL { "" }
    ::= { tlstmAddrEntry 1 }

tlstmAddrServerIdentity OBJECT-TYPE
    SYNTAX      SnmpAdminString
    MAX-ACCESS  read-create
    STATUS      current
    DESCRIPTION
        "The reference identity to check against the identity
        presented by the remote system."
    DEFVAL { "" }
    ::= { tlstmAddrEntry 2 }

tlstmAddrStorageType OBJECT-TYPE
    SYNTAX       StorageType
    MAX-ACCESS   read-create
    STATUS       current



    DESCRIPTION
        "The storage type for this conceptual row.  Conceptual rows
        having the value 'permanent' need not allow write-access to
        any columnar objects in the row."
    DEFVAL      { nonVolatile }
    ::= { tlstmAddrEntry 3 }


tlstmAddrRowStatus OBJECT-TYPE
    SYNTAX      RowStatus
    MAX-ACCESS  read-create
    STATUS      current
    DESCRIPTION
        "The status of this conceptual row.  This object may be used
        to create or remove rows from this table.

        To create a row in this table, an administrator must set this
        object to either createAndGo(4) or createAndWait(5).

        Until instances of all corresponding columns are
        appropriately configured, the value of the
        corresponding instance of the tlstmAddrRowStatus
        column is 'notReady'.

        In particular, a newly created row cannot be made active until
        the corresponding tlstmAddrServerFingerprint column has been
        set.

        Rows MUST NOT be active if the tlstmAddrServerFingerprint
        column is blank and the tlstmAddrServerIdentity is set to '*'
        since this would insecurely accept any presented certificate.

        The tlstmAddrServerFingerprint object may not be modified
        while the value of this object is active(1).

        An attempt to set these objects while the value of
        tlstmAddrRowStatus is active(1) will result in
        an inconsistentValue error."
    ::= { tlstmAddrEntry 4 }


-- ************************************************
--  tlstmNotifications - Notifications Information
-- ************************************************

tlstmServerCertificateUnknown NOTIFICATION-TYPE
    OBJECTS { snmpTlstmSessionUnknownServerCertificate }
    STATUS  current



    DESCRIPTION
        "Notification that the server certificate presented by a SNMP
         over (D)TLS server was invalid because no configured
         fingerprint or CA was acceptable to validate it.  This may
         be because there was no entry in the tlstmAddrTable or
         because no path could be found to known certificate
         authority.

         To avoid notification loops, this notification MUST NOT be
         sent to servers that themselves have triggered the
         notification."
    ::= { tlstmNotifications 1 }

tlstmServerInvalidCertificate NOTIFICATION-TYPE
    OBJECTS { tlstmAddrServerFingerprint,
              snmpTlstmSessionInvalidServerCertificates}
    STATUS  current
    DESCRIPTION
        "Notification that the server certificate presented by an SNMP
         over (D)TLS server could not be validated even if the
         fingerprint or expected validation path was known.  I.E., a
         cryptographic validation occurred during certificate
         validation processing.

         To avoid notification loops, this notification MUST NOT be
         sent to servers that themselves have triggered the
         notification."
    ::= { tlstmNotifications 2 }

-- ************************************************
-- tlstmCompliances - Conformance Information
-- ************************************************

tlstmCompliances OBJECT IDENTIFIER ::= { tlstmConformance 1 }

tlstmGroups OBJECT IDENTIFIER ::= { tlstmConformance 2 }



-- ************************************************
-- Compliance statements
-- ************************************************

tlstmCompliance MODULE-COMPLIANCE
    STATUS      current
    DESCRIPTION
        "The compliance statement for SNMP engines that support the
        TLSTM-MIB"



    MODULE
        MANDATORY-GROUPS { tlstmStatsGroup,
                           tlstmIncomingGroup,
                           tlstmOutgoingGroup,
                           tlstmNotificationGroup }
    ::= { tlstmCompliances 1 }

-- ************************************************
-- Units of conformance
-- ************************************************
tlstmStatsGroup OBJECT-GROUP
    OBJECTS {
        snmpTlstmSessionOpens,
        snmpTlstmSessionClientCloses,
        snmpTlstmSessionOpenErrors,
        snmpTlstmSessionAccepts,
        snmpTlstmSessionServerCloses,
        snmpTlstmSessionNoSessions,
        snmpTlstmSessionInvalidClientCertificates,
        snmpTlstmSessionUnknownServerCertificate,
        snmpTlstmSessionInvalidServerCertificates,
        snmpTlstmSessionInvalidCaches
    }
    STATUS      current
    DESCRIPTION
        "A collection of objects for maintaining
        statistical information of an SNMP engine which
        implements the SNMP TLS Transport Model."
    ::= { tlstmGroups 1 }

tlstmIncomingGroup OBJECT-GROUP
    OBJECTS {
        tlstmCertToTSNCount,
        tlstmCertToTSNTableLastChanged,
        tlstmCertToTSNFingerprint,
        tlstmCertToTSNMapType,
        tlstmCertToTSNData,
        tlstmCertToTSNStorageType,
        tlstmCertToTSNRowStatus
    }
    STATUS      current
    DESCRIPTION
        "A collection of objects for maintaining
        incoming connection certificate mappings to
        tmSecurityNames of an SNMP engine which implements the
        SNMP TLS Transport Model."
    ::= { tlstmGroups 2 }




tlstmOutgoingGroup OBJECT-GROUP
    OBJECTS {
        tlstmParamsCount,
        tlstmParamsTableLastChanged,
        tlstmParamsClientFingerprint,
        tlstmParamsStorageType,
        tlstmParamsRowStatus,
        tlstmAddrCount,
        tlstmAddrTableLastChanged,
        tlstmAddrServerFingerprint,
        tlstmAddrServerIdentity,
        tlstmAddrStorageType,
        tlstmAddrRowStatus
    }
    STATUS      current
    DESCRIPTION
        "A collection of objects for maintaining
        outgoing connection certificates to use when opening
        connections as a result of SNMP-TARGET-MIB settings."
    ::= { tlstmGroups 3 }

tlstmNotificationGroup NOTIFICATION-GROUP
    NOTIFICATIONS {
        tlstmServerCertificateUnknown,
        tlstmServerInvalidCertificate
    }
    STATUS current
    DESCRIPTION
        "Notifications"
    ::= { tlstmGroups 4 }

END
